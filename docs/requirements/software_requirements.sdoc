[DOCUMENT]
TITLE: Software Requirements

[GRAMMAR]
IMPORT_FROM_FILE: grammar.sgra

[SW_REQUIREMENT]
UID: SWR-001
TITLE: HAL Interface Definition
STATEMENT: Der HardwareDriver Interface muss alle Hardware-Operationen (BME280, GPIO, UART, SPI) abstrakt definieren, sodass verschiedene Backends austauschbar sind.
STATUS: Active
PRIORITY: High
RELATIONS:
- TYPE: Parent
  VALUE: SYS-004
- TYPE: File
  VALUE: go-api/pkg/hal/interface.go
- TYPE: File
  VALUE: go-api/pkg/hal/hal_test.go

[SW_REQUIREMENT]
UID: SWR-002
TITLE: Backend-Auswahl per Umgebungsvariable
STATEMENT: Das System muss über die Umgebungsvariable HW_BACKEND die Auswahl des Hardware-Backends (c, rust, auto) ermöglichen. Der Standardwert ist auto.
STATUS: Active
PRIORITY: High
RELATIONS:
- TYPE: Parent
  VALUE: SYS-004
- TYPE: File
  VALUE: go-api/pkg/hal/loader/factory.go
- TYPE: File
  VALUE: tests/api/test_api.py

[SW_REQUIREMENT]
UID: SWR-003
TITLE: Mock Driver für Tests
STATEMENT: Der Mock Driver muss das HardwareDriver Interface vollständig implementieren und darf keine echte Hardware benötigen.
STATUS: Active
PRIORITY: Medium
RELATIONS:
- TYPE: Parent
  VALUE: SWR-001
- TYPE: File
  VALUE: go-api/pkg/hal/mock/driver.go
- TYPE: File
  VALUE: go-api/pkg/hal/hal_test.go

[SW_REQUIREMENT]
UID: SWR-004
TITLE: Hardware-Zugriff nur in C und Rust
STATEMENT: Hardware-Zugriffe dürfen ausschließlich in C und Rust implementiert werden. Go darf nicht direkt auf Hardware zugreifen.
STATUS: Active
PRIORITY: High
RELATIONS:
- TYPE: Parent
  VALUE: SYS-004
- TYPE: File
  VALUE: go-api/pkg/hal/c/driver.go
- TYPE: File
  VALUE: go-api/pkg/hal/rust/driver.go
- TYPE: File
  VALUE: c-lib/include/bme280.h
- TYPE: File
  VALUE: rust-lib/src/lib.rs

[SW_REQUIREMENT]
UID: SWR-005
TITLE: Auto-Fallback Mechanismus
STATEMENT: Im Backend-Modus auto muss das System zunächst das C-Backend versuchen und bei Fehler automatisch auf das Rust-Backend zurückfallen.
STATUS: Active
PRIORITY: Medium
RELATIONS:
- TYPE: Parent
  VALUE: SWR-002
- TYPE: File
  VALUE: go-api/pkg/hal/loader/factory.go
- TYPE: File
  VALUE: go-api/pkg/hal/hal_test.go

[SW_REQUIREMENT]
UID: SWR-008
TITLE: Keine flag.Parse() in Library-Packages
STATEMENT: Library-Packages dürfen flag.Parse() nicht aufrufen und keine Flags im globalen flag.CommandLine registrieren. Konfigurationswerte müssen ausschließlich über Umgebungsvariablen oder Dependency Injection übergeben werden.
STATUS: Active
PRIORITY: High
RELATIONS:
- TYPE: Parent
  VALUE: SWR-002
- TYPE: File
  VALUE: go-api/pkg/hal/config/config.go
- TYPE: File
  VALUE: go-api/pkg/hal/config/config_test.go

[TEST_CASE]
UID: TC-008
TITLE: LoadConfig registriert keine Flags im globalen FlagSet
STATEMENT: Verifiziert, dass LoadConfig() keine Flags (backend, uart, i2c) im globalen flag.CommandLine registriert und flag.Parse() nicht aufruft.
TEST_TYPE: Unit
RELATIONS:
- TYPE: Parent
  VALUE: SWR-008
- TYPE: File
  VALUE: go-api/pkg/hal/config/config_test.go

[SW_REQUIREMENT]
UID: SWR-007
TITLE: BME280 Stream Flusher-Prüfung
STATEMENT: Der BME280StreamHandler muss vor dem Streaming prüfen ob der ResponseWriter das http.Flusher-Interface implementiert. Falls nicht, muss HTTP 500 zurückgegeben werden anstatt einen Panic auszulösen.
STATUS: Active
PRIORITY: High
RELATIONS:
- TYPE: Parent
  VALUE: SWR-001
- TYPE: File
  VALUE: go-api/pkg/api/handlers.go
- TYPE: File
  VALUE: go-api/pkg/api/handlers_test.go

[TEST_CASE]
UID: TC-007
TITLE: BME280StreamHandler gibt 500 zurück wenn kein Flusher
STATEMENT: Verifiziert, dass BME280StreamHandler HTTP 500 zurückgibt wenn der ResponseWriter kein http.Flusher implementiert, anstatt einen Panic zu verursachen.
TEST_TYPE: Unit
RELATIONS:
- TYPE: Parent
  VALUE: SWR-007
- TYPE: File
  VALUE: go-api/pkg/api/handlers_test.go

[SW_REQUIREMENT]
UID: SWR-006
TITLE: HTTP-Server Timeouts
STATEMENT: Der HTTP-Server muss ReadTimeout, WriteTimeout und IdleTimeout konfigurieren, um auf eingebetteten Systemen Ressourcenerschöpfung durch hängende Verbindungen zu verhindern. ReadTimeout >= 5s, WriteTimeout >= 10s, IdleTimeout >= 30s.
STATUS: Active
PRIORITY: High
RELATIONS:
- TYPE: Parent
  VALUE: SYS-004
- TYPE: File
  VALUE: go-api/pkg/api/server.go
- TYPE: File
  VALUE: go-api/pkg/api/server_test.go

[TEST_CASE]
UID: TC-006
TITLE: HTTP-Server hat konfigurierte Timeouts
STATEMENT: Verifiziert, dass NewHTTPServer einen http.Server mit ReadTimeout, WriteTimeout und IdleTimeout > 0 zurückgibt.
TEST_TYPE: Unit
RELATIONS:
- TYPE: Parent
  VALUE: SWR-006
- TYPE: File
  VALUE: go-api/pkg/api/server_test.go

[SW_REQUIREMENT]
UID: HW-API-007
TITLE: POST-Handler JSON-Validierung
STATEMENT: Alle POST-Handler der REST API müssen den JSON-Request-Body validieren und bei ungültigem JSON oder fehlenden Pflichtfeldern HTTP 400 Bad Request zurückgeben, bevor Hardware-Operationen aufgerufen werden.
STATUS: Active
PRIORITY: High
RELATIONS:
- TYPE: Parent
  VALUE: SWR-001
- TYPE: File
  VALUE: go-api/pkg/api/handlers.go
- TYPE: File
  VALUE: go-api/pkg/api/handlers_test.go

[TEST_CASE]
UID: TC-005
TITLE: POST-Handler 400 bei ungültigem JSON
STATEMENT: Verifiziert, dass alle POST-Handler bei ungültigem JSON-Body HTTP 400 zurückgeben und keine Hardware-Operationen mit Null-Werten ausführen.
TEST_TYPE: Unit
RELATIONS:
- TYPE: Parent
  VALUE: HW-API-007
- TYPE: File
  VALUE: go-api/pkg/api/handlers_test.go

[SOURCE_CODE]
UID: SC-001
TITLE: HAL Interface
STATEMENT: Definiert das HardwareDriver Interface für alle Hardware-Backends.
LANGUAGE: Go
RELATIONS:
- TYPE: Parent
  VALUE: SWR-001
- TYPE: File
  VALUE: go-api/pkg/hal/interface.go

[SOURCE_CODE]
UID: SC-002
TITLE: Mock Driver
STATEMENT: Test-Implementierung des HardwareDriver Interface ohne echte Hardware.
LANGUAGE: Go
RELATIONS:
- TYPE: Parent
  VALUE: SWR-003
- TYPE: File
  VALUE: go-api/pkg/hal/mock/driver.go

[SOURCE_CODE]
UID: SC-003
TITLE: Backend Factory
STATEMENT: Wählt das aktive Hardware-Backend anhand der HW_BACKEND Umgebungsvariable.
LANGUAGE: Go
RELATIONS:
- TYPE: Parent
  VALUE: SWR-002
- TYPE: File
  VALUE: go-api/pkg/hal/loader/factory.go

[TEST_CASE]
UID: TC-001
TITLE: BME280 Lesen Erfolg
STATEMENT: Verifiziert, dass BME280Read() gültige Messwerte zurückgibt.
TEST_TYPE: Unit
RELATIONS:
- TYPE: Parent
  VALUE: SWR-001
- TYPE: File
  VALUE: go-api/pkg/hal/hal_test.go

[TEST_CASE]
UID: TC-002
TITLE: GPIO Schreiben und Lesen
STATEMENT: Verifiziert GPIO-Schreib- und Leseoperation über den Mock Driver.
TEST_TYPE: Unit
RELATIONS:
- TYPE: Parent
  VALUE: SWR-003
- TYPE: File
  VALUE: go-api/pkg/hal/hal_test.go

[TEST_CASE]
UID: TC-003
TITLE: Auto-Fallback bei C-Fehler
STATEMENT: Verifiziert, dass das System bei C-Backend-Fehler auf Rust zurückfällt.
TEST_TYPE: Unit
RELATIONS:
- TYPE: Parent
  VALUE: SWR-005
- TYPE: File
  VALUE: go-api/pkg/hal/hal_test.go

[TEST_CASE]
UID: TC-004
TITLE: API Backend-Wechsel
STATEMENT: Verifiziert, dass HW_BACKEND per REST API umgeschaltet werden kann.
TEST_TYPE: Integration
RELATIONS:
- TYPE: Parent
  VALUE: SWR-002
- TYPE: File
  VALUE: tests/api/test_api.py
